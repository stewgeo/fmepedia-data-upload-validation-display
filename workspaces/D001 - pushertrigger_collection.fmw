FME workspace D001 - pushertrigger_collection.fmw

Parameters:
- type = i   # Type
- list =   # List
- counter = 1
- DATASET = xe   # Dataset
- ORACLE8I_USER_NAME = STEWART   # ORACLE8I Username
- ORACLE8I_PASSWORD =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   # ORACLE8I Password
- USERNAME = fmepedia   # Username
- PASSWORD =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   # PASSWORD Password
- appid = 18486   # Pusher appID
- key = eb28a88582cbfd79aea5   # Pusher Key
- secret = f47cb9485c5a559df0eb   # Pusher secret

Creator
    NUM = 1
    GEOMTYPE = Geometry Object
    CREATED -> ParameterFetcher
ParameterFetcher
    ATTR_LIST = _type {$(type)} _list {$(list)} _counter {$(counter)}
    -> TestFilter
TestFilter
    TEST_LIST = BOOL_OP,OR,COMPOSITE_TEST,<Unused>,TEST_CLAUSE,"TEST ""@Value(_type)"" = ""i""",_type = i,BOOL_OP,OR,COMPOSITE_TEST,<Unused>,TEST_CLAUSE,"TEST ""@Value(_type)"" = ""d""",_type = d,BOOL_OP,OR,COMPOSITE_TEST,<Unused>,TEST_CLAUSE,"TEST ""@Value(_type)"" = ""u""",_type = u
    _type = i -> StringReplacer
StringReplacer
    SRC_ATTRS = _list
    REGEXP = no
    CASE = no
    REPLACE_TEXT = '
    FIND_TEXT = "
    -> Decelerator
Decelerator
    DECEL_TYPE = Per Feature Delay
    DELAY = 1
    -> FeatureReader
FeatureReader
    WHERE = FEATURE_ID IN (@Value(_list))
    ORACLE8I_SERVER_TYPE = ORACLE8i
    ORACLE8I_TABLELIST = STEWART.WATERLINES
    ATTRIBUTES = STEWART.WATERLINES,"PRIMARYINDEX,PROJECT,SYMCODE,ANNO_DIAM,FEATURE_ID,LEAD_MAIN_,MATERIAL,STATUS,DRAW,AUTOCAD_ELEVATION,WNM_TYPE,COMPKEY,SYMCODE2,PR_ZONE,DIAMETER,COMPTYPE,TILE,BULK_LOAD,YEAR_INSTA"
    FEATURETYPES = STEWART.WATERLINES
    SUPPORTED_SPATIAL_INTERACTIONS = ENVELOPE_INTERSECT%ORACLE:ANYINTERACT%ORACLE:CONTAINS%ORACLE:COVEREDBY%ORACLE:COVERS%ORACLE:EQUAL%ORACLE:INSIDE%ORACLE:ON%ORACLE:OVERLAPBDYDISJOINT%ORACLE:OVERLAPBDYINTERSECT%ORACLE:TOUCH%INTERSECTS%EQUALS%OVERLAPS%TOUCHES%CONTAINS%CROSSES%DISJOINT%WITHIN
    ORACLE8I_PERSISTENT_CONNECTION = YES
    DATASET = XE
    ORACLE8I_PARSE_MAPINFO_SYMBOLOGY = NO
    ORACLE8I_USER_NAME = STEWART
    ORACLE8I_READ_3D_POLYGON_AS_FACE = NO
    COMBINE_GEOM = Result Geometry Only
    COMBINE_ATTRS = Result Attributes Only
    FORMAT = ORACLE8I
    ORACLE8I_PASSWORD = STEWART
    ORACLE8I_REMOVE_SCHEMA_QUALIFIER = NO
    STEWART.WATERLINES -> Reprojector
    INITIATOR -> AttributeExposer
Reprojector
    DEST = EPSG:4326
    RASTER_CELL_SIZE = Preserve Cells
    STROKE_ARCS = Yes
    SOURCE = Read from feature
    INTERPOLATION_TYPE_NAME = Nearest Neighbor
    REPROJECTED -> GeometryExtractor
GeometryExtractor
    ATTR = _geometryupdated
    KIND_LONG = GeoJSON
    -> ParameterFetcher_2
ParameterFetcher_2
    ATTR_LIST = _type {$(type)}
    -> StringConcatenator_3
StringConcatenator_3
    PARM_LINE = {"id" : "@Value(FEATURE_ID)","type": "@Value(_type)","features" : [ @Value(_geometryupdated)]}
    VAL_ATTR = _stringinsertupdate
    -> PusherRunner
PusherRunner
    appid = $(appid)
    event = message
    key = $(key)
    channel = lobby
    secret = $(secret)
    message = _stringinsertupdate
AttributeExposer
    ATTR_LIST = _matched_records
    -> Tester
Tester
    TEST_MODE = Automatic
    TEST_DESCRIPTION = ""
    BOOL_OP = OR
    TEST_CLAUSE = TEST "@Value(_matched_records)" = "0"
    PASSED -> Tester_2
    FAILED -> SQLExecutor
Tester_2
    TEST_MODE = Automatic
    TEST_DESCRIPTION = ""
    BOOL_OP = OR
    TEST_CLAUSE = TEST "@Value(_counter)" < "15"
    PASSED -> ExpressionEvaluator
ExpressionEvaluator
    VAL_ATTR = _result
    EXPRESSION = @Value(_counter)+1
    -> FMEServerJobSubmitter
FMEServerJobSubmitter
    PASSWORD = $(PASSWORD)
    USERNAME = $(USERNAME)
    SERVER_NAME = http://localhost
    WORKSPACE_NAME = D001 - pushertrigger_collection.fmw
    BLOCKING = No
    REPOSITORY = fmepedia_demos
    SERVER_PORT = 0
    WORKSPACE_PARAMETERS = type,@Value(_type),list,@Value(_list),counter,@Value(_result)
    SUBSECTION = SERVER_JOB_SUBMITTER
    PRIORITY = 100
Note: Delete Elements from temp Table
SQLExecutor
    ORACLE8I_SERVER_TYPE = ORACLE8i
    SQL_STATEMENT = DELETE FROM temp_ids WHERE feature_id IN (@Value(_list))
    ORACLE8I_PERSISTENT_CONNECTION = YES
    DATASET = $(DATASET)
    ORACLE8I_USER_NAME = $(ORACLE8I_USER_NAME)
    COMBINE_GEOM = Initiator Geometry Only
    COMBINE_ATTRS = Result Attributes Only
    FORMAT = ORACLE8I
    ORACLE8I_REMOVE_SCHEMA_QUALIFIER = NO
    ORACLE8I_PASSWORD = $(ORACLE8I_PASSWORD)

FME custom transformer PusherRunner
This transformer simply sends the content of an attribute to the Pusher web service (http://pusher.com/).
Before using this transformer, the following Python modules have to be installed:
Python setuptools setup (Windows)
Download and unzip the setuptools source (IMPORTANT: This works only with the source package)
Open the Windows Command Prompt
Go to the setuptools directory
Adapt and enter the following code:
<path_to_FME>\fme.exe python setup.py install
Pusher Python module setup (Windows)
Download and unzip the python module
Open the Windows Command Prompt
Go to the Pusher Python module directory
Enter the following code:
<path_to_FME>\fme.exe python setup.py install
Further, a Pusher login is necessary. 
The configuration parameters appid, key and secret are defined in the API access menu point on the Pusher homepage.
Channel and event can be chosen by the user.
After a successful configuration, the transformer sends the content of every message attribute passed in to Pusher.
HINT: All incoming messages are logged in the Debug console on the Pusher homepage.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- appid =   # Pusher appID
- key =   # Pusher Key
- secret =   # Pusher secret
- channel =   # Pusher channel
- event =   # Pusher event
- message =   # " " Message attribute

INPUT (input)
    -> ParameterFetcher
ParameterFetcher
    ATTR_LIST = _appid {$(appid)} _key {$(key)} _secret {$(secret)} _channel {$(channel)} _event {$(event)} _message_attribute {$(message)}
    -> PythonCaller
PythonCaller
    PYTHONSOURCE:
      import sys
      import pusher

      # Template Class Interface:
      class FeatureProcessor(object):
          def __init__(self):
              pass

          def input(self,feature):
              pusher.app_id = feature.getAttribute("_appid")

              pusher.key = feature.getAttribute("_key")

              pusher.secret = str(feature.getAttribute("_secret"))

              p = pusher.Pusher()

              channel = str(feature.getAttribute("_channel"))
              event = str(feature.getAttribute("_event"))

              p[channel].trigger(event, feature.getAttribute(feature.getAttribute("_message_attribute")))
              self.pyoutput(feature)


          def close(self):
              pass
    PYTHONSYMBOL = FeatureProcessor
