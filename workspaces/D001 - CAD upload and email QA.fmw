FME workspace D001 - CAD upload and email QA.fmw
Title: CAD & GIS Workflow - 3. CAD Data Validation & Load
Description: CAD & GIS Workflow for FME Server (FME 2011)
Workspace uploads the CAD data, validates the DWG file and if validation is successful loads the DWG into the database. 
If the validation fails, an HTML report of the bad features is generated.

Parameters:
- SourceDataset_TEXTLINE = C:\tmp\email_json_content.txt   # Source Text File(s)
- DestDataset_ORACLE8I = xe   # Destination Oracle Spatial Object Service
- HTTP_AUTH_USERNAME = fmepedia   # Username
- HTTP_AUTH_PASSWORD =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   # Password

Readers:
- TEXTLINE_1: TEXTLINE from $(SourceDataset_TEXTLINE)

Writers:
- ORACLE8I_1: ORACLE8I to $(DestDataset_ORACLE8I)

text_line (reader TEXTLINE_1)
    attributes: text_line_data buffer
    -> JSONFlattener
JSONFlattener
    RECURSIVE = Yes
    JSON_ATTR = text_line_data
    -> AttributeExposer
AttributeExposer
    ATTR_LIST = email_relay_attachment{},email_relay_to,email_relay_received,email_relay_subject,email_relay_from,email_relay_sent,""
    -> FeatureReader
FeatureReader
    ACAD_RESOLVE_BLOCKS = yes
    ACAD_PRESERVE_COMPLEX_HATCHES = no
    ACAD_METAFILE = acadScan
    FEATURETYPES = water_distribution_lines
    ACAD_VISIBLE_ATTRIBUTES_AS_TEXT = yes
    COMBINE_GEOM = Result Geometry Only
    ACAD_IGNORE_UCS = no
    ACAD_STORE_INSERT_POINT = no
    ACAD_READ_AS_2_5D = no
    ACAD_APPLY_WORLD_FILE = yes
    ACAD_STORE_LAYER_INFO = no
    ACAD_READ_PAPER_SPACE = no
    COMBINE_ATTRS = Keep Result Attributes if Conflict
    SUPPORTED_SPATIAL_INTERACTIONS = ENVELOPE_INTERSECT%INTERSECTS%CONTAINS%CROSSES%DISJOINT%EQUALS%OVERLAPS%TOUCHES%WITHIN
    ACAD_EXPLODE_MTEXT = yes
    DATASET = @Value(email_relay_attachment{0})
    ACAD_READ_GROUPS = no
    ATTRIBUTES = water_distribution_lines,"PROJECT,SYMCODE,ANNO_DIAM,FEATURE_ID,autocad_elevation,LEAD_MAIN_,MATERIAL,STATUS,DRAW,WNM_TYPE,COMPKEY,SYMCODE2,PR_ZONE,DIAMETER,COMPTYPE,TILE,YEAR_INSTA",water_distribution_nodes,"FEATURE_ID,TILE",water_meters,
    ACAD_USE_BLOCK_HEADER_LAYER = yes
    FORMAT = ACAD
    ACAD_RESOLVE_ENTITY_COLOR = yes
    water_distribution_lines -> GeometryFilter
    water_distribution_lines -> FeatureHolder
GeometryFilter
    BREAK_AGG = No
    LINE -> VariableSetter_2
VariableSetter_2
    SCOPE = Global
    VALUE = @Value(email_relay_from)
    VARNAME = email_from_global
    -> VariableSetter_3
VariableSetter_3
    SCOPE = Global
    VALUE = @Value(email_relay_attachment{0})
    VARNAME = email_attachment_global
    -> GeometryOGCValidator
GeometryOGCValidator
    VALIDATION_TYPE = Simple
    PASSED -> Tester
    FAILED -> VariableSetter
VariableSetter
    SCOPE = Global
    VALUE = yes
    VARNAME = _invalidFeatures
    -> XMLTemplater
XMLTemplater
    RESULT_ATTRIBUTE = Remarks
    ROOT_QUERY_EXPR:
      <div style="min-width: 200px;">Invalid Geometry
      </div>
    VISIBLE_QUERY_VALIDATE = No
    OUTPUT_XML_HEADER = Yes
    -> AttributeCreator
AttributeCreator
    ATTR_LIST = _invalid_features,yes
    -> GoogleStaticMapCreator
Tester
    TEST_MODE = Automatic
    TEST_DESCRIPTION = ""
    BOOL_OP = OR
    TEST_LIST = &DIAMETER,=,0,&DIAMETER,=,""
    TEST_CLAUSE = TEST "@Value(DIAMETER)" = "0"
    PASSED -> VariableSetter_4
VariableSetter_4
    SCOPE = Global
    VALUE = yes
    VARNAME = _invalidFeatures
    -> XMLTemplater_3
XMLTemplater_3
    RESULT_ATTRIBUTE = Remarks
    ROOT_QUERY_EXPR:
      <div>Invalid Attribute: DIAMETER
      </div>
    VISIBLE_QUERY_VALIDATE = No
    OUTPUT_XML_HEADER = Yes
    -> AttributeCreator_2
AttributeCreator_2
    ATTR_LIST = _invalid_features,yes
    -> GoogleStaticMapCreator
GoogleStaticMapCreator
    StringConcatenator_5_OUTPUT_172 -> XMLTemplater_2 [input 2]
Note: Hold the features until step 1 / above has completed.
FeatureHolder
    -> VariableRetriever
VariableRetriever
    SCOPE = Global
    VARNAME = _invalidFeatures
    VALUE_ATTR = _invalidFeatures
    -> Tester_3
Tester_3
    TEST_MODE = Automatic
    TEST_DESCRIPTION = ""
    BOOL_OP = OR
    TEST_LIST = &_invalidFeatures,!=,yes
    TEST_CLAUSE = TEST "@Value(_invalidFeatures)" != "yes"
    PASSED -> Sampler
    PASSED -> AttributeCreator_4
Sampler
    RATE = 1
    SAMPLE_TYPE_LONG = First N Features
    SAMPLED -> AttributeCreator_3
Note: Set-up DELETE of TILE N25 / using fme_db_operation and / fme_where / One feature deletes all the tile - / could have used SQLExecutor
AttributeCreator_3
    ATTR_LIST = fme_db_operation,DELETE,fme_where,TILE = 'N25'
    -> STEWART.WATERLINES (writer ORACLE8I_1)
Note: Set-up INSERT of new / TILE N25 records
AttributeCreator_4
    ATTR_LIST = fme_db_operation,INSERT
    -> FeatureHolder_2
FeatureHolder_2
    -> Counter
Counter
    SCOPE = Global
    START = 0
    DOMAIN = _PrimaryIndex
    CNT_ATTR = PRIMARYINDEX
    -> FeatureTypeFilter
FeatureTypeFilter
    ATTRIBUTES = water_distribution_lines,water_meters,water_distribution_nodes
    water_distribution_lines -> AttributeCopier
    water_distribution_lines -> STEWART.WATERLINES (writer ORACLE8I_1)
AttributeCopier
    ATTR_LIST = email_attach,email_relay_attachment{0}
    -> StatisticsCalculator
StatisticsCalculator
    GROUP_BY = email_attach
    STATS_ATTR = PRIMARYINDEX
    PASS_THROUGH = No
    MAX_ATTR = _max
    RANGE_ATTR = _range
    SUM_ATTR = _sum
    COUNT_ATTR = _count
    NUMERIC_ATTR = _numeric_count
    STDEV_ATTR = _stdev
    MODE_ATTR = _mode
    MEDIAN_ATTR = _median
    MIN_ATTR = _min
    MEAN_ATTR = _mean
    STATISTICS -> AttributeCreator_5
AttributeCreator_5
    ATTR_LIST = Remarks,Load Complete - Data Validation was Successful,FEATURE_ID, ,WNM_TYPE,,DIAMETER,
    -> TimeStamper
TimeStamper
    FMT = "^x "
    TIME_ATTR = INSTALLED
    -> TimeStamper_2
TimeStamper_2
    FMT = ^X
    TIME_ATTR = INSTALLEDtime
    -> StringConcatenator
StringConcatenator
    PARM_LINE:
      <!doctype html>
      <head>
        <meta charset="utf-8">

        <!-- Use the .htaccess and remove these lines to avoid edge case issues. More info: h5bp.com/i/378 -->
        <meta http-equiv="X-UA-Compatible" content="IE=edge,chrome=1">

        <title></title>
        <meta name="description" content="">

        <!-- Mobile viewport optimized: h5bp.com/viewport -->
        <meta name="viewport" content="width=device-width">


      </head>
      <body>
      	@Value(Remarks)<br>Date Loaded:  @Value(INSTALLED)  @Value(INSTALLEDtime)<br>Number of Features Added: @Value(_count)
      </body>
      </html>
    VAL_ATTR = _result
    -> UUIDGenerator
UUIDGenerator
    UUID_ATTR = _uuid
    -> StringConcatenator_4
StringConcatenator_4
    PARM_LINE = c:/temp/@Value(_uuid).html
    VAL_ATTR = filename
    -> AttributeFileWriter
AttributeFileWriter
    CHAR_ENCODING = fme-system
    FILE_NAME = @Value(filename)
    SOURCE_ATTR = _result
    -> FilenamePartExtractor
FilenamePartExtractor
    SRC_ATTR = email_attach
    TGT_ATTR = submitted_file
    FILENAME_PART = Full Filename
    -> VariableRetriever_5
Note: Retrieve Email to send to
VariableRetriever_5
    SCOPE = Global
    VARNAME = email_from_global
    VALUE_ATTR = email_from_global
    -> StringConcatenator_2
StringConcatenator_2
    PARM_LINE:
      {
      email_to:"@Value(email_from_global)",
      email_attachment: "@Value(filename)",
      email_subject: "QA for file @Value(submitted_file) succeeded!",
      subscriber_content: "File @Value(submitted_file) has been loaded into the central repository database."
      }
    VAL_ATTR = success_email_content
    -> FMEServerNotifier
FMEServerNotifier
    HTTP_UPLOAD_BODY = success_email_content
    HTTP_AUTH_PASSWORD = $(HTTP_AUTH_PASSWORD)
    STATUS_CODE_ATTR = _http_status_code
    TOPIC = cad_waterqa_success
    HTTP_AUTH_USERNAME = $(HTTP_AUTH_USERNAME)
    URL = localhost
Note: After finishing the writing process / a stored function is called to send an HTTP request / (see SQL statement to execute after translation paramerter)
STEWART.WATERLINES (writer ORACLE8I_1)
    attributes: ANNO_DIAM varchar2(255), COMPKEY number(38,0), COMPTYPE number(38,0), DIAMETER varchar2(255), DRAW number(38,0), FEATURE_ID varchar2(25), LEAD_MAIN_ number(38,0), MATERIAL varchar2(8), PRIMARYINDEX number(38,0), PROJECT varchar2(255), PR_ZONE varchar2(4), STATUS varchar2(3), SYMCODE number(38,0), SYMCODE2 number(38,0), TILE varchar2(4), WNM_TYPE varchar2(8), YEAR_INSTA number(38,0), AUTOCAD_ELEVATION number(38,0), BULK_LOAD number(38,0)
Creator
    NUM = 1
    GEOMTYPE = Geometry Object
    CREATED -> VariableRetriever_3
VariableRetriever_3
    SCOPE = Global
    VARNAME = _invalidFeatures
    VALUE_ATTR = _invalidFeatures
    -> Tester_2
Tester_2
    TEST_MODE = Automatic
    TEST_DESCRIPTION = ""
    BOOL_OP = OR
    TEST_LIST = &_invalidFeatures,!=,yes
    TEST_CLAUSE = TEST "@Value(_invalidFeatures)" = "yes"
    PASSED -> XMLTemplater_2 [input 1]
XMLTemplater_2
    RESULT_ATTRIBUTE = _htmlTable
    ROOT_QUERY_EXPR:
      <table style="line-height: 1.6em;font-family: 'Lucida Sans Unicode', 'Lucida Grande', Sans-Serif;font-size: 12px;background: #fff;margin: 45px;width: 480px;border-collapse: collapse;text-align: left;" id="hor-minimalist-a">
      <tr>
      <th style="font-size: 14px;font-weight: normal;color: #039;padding: 10px 8px;border-bottom: 2px solid #6678b1;">TILE</th>
      <th style="font-size: 14px;font-weight: normal;color: #039;padding: 10px 8px;border-bottom: 2px solid #6678b1;">FEATURE_ID</th>
      <th style="font-size: 14px;font-weight: normal;color: #039;padding: 10px 8px;border-bottom: 2px solid #6678b1;">DIAMETER</th>
      <th style="font-size: 14px;font-weight: normal;color: #039;padding: 10px 8px;border-bottom: 2px solid #6678b1;">WNM_TYPE</th>
      <th style="font-size: 14px;font-weight: normal;color: #039;padding: 10px 8px;border-bottom: 2px solid #6678b1;">Error Remarks</th>
      <th style="font-size: 14px;font-weight: normal;color: #039;padding: 10px 8px;border-bottom: 2px solid #6678b1;">Map</th>
      </tr>
      {fme:process-features("ROW")}
      </table>
    VISIBLE_QUERY_VALIDATE = No
    ROW_QUERY_EXPR:
      <tr>
      <td style="	color: #669;padding: 9px 8px 0px 8px;" >{fme:get-attribute("TILE")}</td>
      <td style="	color: #669;padding: 9px 8px 0px 8px;">{fme:get-attribute("FEATURE_ID")}</td>
      <td style="	color: #669;padding: 9px 8px 0px 8px;">{fme:get-attribute("DIAMETER")}</td>
      <td style="	color: #669;padding: 9px 8px 0px 8px;">{fme:get-attribute("WNM_TYPE")}</td>
      <td style="	color: #669;padding: 9px 8px 0px 8px;">{fme:get-xml-attribute("Remarks")}</td>
      <td style="	color: #669;padding: 9px 8px 0px 8px;"><img src="{fme:get-attribute("_StaticMapUrl")}"></img></td>
      </tr>
    OUTPUT_XML_HEADER = No
    -> HTMLTemplate
HTMLTemplate
    -> AttributeExposer_2
AttributeExposer_2
    ATTR_LIST = email_from_global
    -> UUIDGenerator_2
UUIDGenerator_2
    UUID_ATTR = _uuid
    -> StringConcatenator_6
StringConcatenator_6
    PARM_LINE = c:/temp/@Value(_uuid).html
    VAL_ATTR = filename
    -> AttributeFileWriter_2
Note: Write html file to temp DIR
AttributeFileWriter_2
    CHAR_ENCODING = fme-system
    FILE_NAME = @Value(filename)
    SOURCE_ATTR = _htmlFull
    -> VariableRetriever_2
Note: Retrieve Email to send to
VariableRetriever_2
    SCOPE = Global
    VARNAME = email_from_global
    VALUE_ATTR = email_from_global
    -> VariableRetriever_4
VariableRetriever_4
    SCOPE = Global
    VARNAME = email_attachment_global
    VALUE_ATTR = email_attachment_global
    -> FilenamePartExtractor_2
FilenamePartExtractor_2
    SRC_ATTR = email_attachment_global
    TGT_ATTR = submitted_file
    FILENAME_PART = Full Filename
    -> StringConcatenator_3
Note: Build JSON up.
StringConcatenator_3
    PARM_LINE:
      {
      email_to:"@Value(email_from_global)",
      email_attachment: "@Value(filename)",
      email_subject: "QA for file @Value(submitted_file) failed!",
      subscriber_content: "File @Value(submitted_file) has errors and therefore has NOT been loaded into the central repository database. See the attached html file for details of the errors."
      }
    VAL_ATTR = fail_email_content
    -> FMEServerNotifier_2
    -> Logger_2
Logger_2
    MESSAGE = Feature is:
    MAXFEATS = 20
    MAXCOORDS = 20
Note: Send notification
FMEServerNotifier_2
    HTTP_UPLOAD_BODY = fail_email_content
    HTTP_AUTH_PASSWORD = $(HTTP_AUTH_PASSWORD)
    STATUS_CODE_ATTR = _http_status_code
    TOPIC = cad_waterqa_fail
    HTTP_AUTH_USERNAME = $(HTTP_AUTH_USERNAME)
    URL = localhost

Bookmark: Creates Web HTML Forrm with Report
Note: Uses Template HTML Table / Replaces Values

FME custom transformer GoogleStaticMapCreator

GeometryExtractor_INPUT_197 (input)
    -> Reprojector
Reprojector
    DEST = EPSG:4326
    RASTER_CELL_SIZE = Preserve Cells
    STROKE_ARCS = Yes
    SOURCE = TX83-CF
    INTERPOLATION_TYPE_NAME = Nearest Neighbor
    REPROJECTED -> CoordinateSwapper
CoordinateSwapper
    SWAP_TYPE = X <-> Y
    -> GeometryExtractor
GeometryExtractor
    OGCVERSION = 1.1
    ATTR = _geometry
    KIND_LONG = OGC Well Known Text
    -> SubstringExtractor
SubstringExtractor
    RESULT_ATTR = _path
    SRC_ATTR = _geometry
    START = 12
    END = -2
    -> StringReplacer_2
StringReplacer_2
    SRC_ATTRS = _path
    REGEXP = no
    CASE = no
    REPLACE_TEXT = |
    FIND_TEXT = ,
    -> StringReplacer
StringReplacer
    SRC_ATTRS = _path
    REGEXP = no
    CASE = no
    REPLACE_TEXT = ,
    FIND_TEXT = " "
    -> CoordinateExtractor
CoordinateExtractor
    Y_ATTR = _y
    X_ATTR = _x
    Z_DEFAULT = -9999
    Z_ATTR = _z
    IND = 0
    -> StringConcatenator_5
StringConcatenator_5
    PARM_LINE = fme_basicstring:53%10%1%10%68%13:http://maps.googleapis.com/maps/api/staticmap?center=@Value(_x),@Value(_y)&amp&amp&size=200x200&amp&sensor=false&path=color:0x0000ff|weight:5|@Value(_path)
    VAL_ATTR = _StaticMapUrl
    -> StringConcatenator_5_OUTPUT_172 (output)
StringConcatenator_5_OUTPUT_172 (output)

FME custom transformer HTMLTemplate

INPUT (input)
    -> StringConcatenator
StringConcatenator
    PARM_LINE:
      <!DOCTYPE html>
      <html>
      <head>
        <meta charset="utf-8">

        <!-- Use the .htaccess and remove these lines to avoid edge case issues. More info: h5bp.com/i/378 -->
        <meta http-equiv="X-UA-Compatible" content="IE=edge,chrome=1">

        <title>Data validation failure</title>
        <meta name="description" content="">

        <!-- Mobile viewport optimized: h5bp.com/viewport -->
        <meta name="viewport" content="width=device-width">

        <!-- CSS goes in the document HEAD or added to your external stylesheet -->
      <style type="text/css">
      /* ------------------
       styling for the tables
         ------------------   */




      </style>

      </head>
      <body>
      @Value(_htmlTable)

      </body>
      </html>
    VAL_ATTR = _htmlFull
    -> OUTPUT (output)
OUTPUT (output)
